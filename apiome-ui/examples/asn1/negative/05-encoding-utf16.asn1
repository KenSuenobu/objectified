﻿-- The smallest canonical module, saved as UTF-16 so the importer's UTF-8
-- decode produces replacement characters.
MinimalModule DEFINITIONS ::= BEGIN

  Ping ::= SEQUENCE {
    message  UTF8String
  }

END
